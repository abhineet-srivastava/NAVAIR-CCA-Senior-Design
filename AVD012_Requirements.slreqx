# AVD012_Requirements
AVD-012 requirement flow-down: RFP requirements decompose into System-level requirements, which decompose into Subsystem-level (derived) requirements. Generated from the traceability matrix by build_avd012_requirements.m.

## #1: RFP Requirements (Container)

### RFP-3.1.b.b: General Design – Propulsion (Functional)
Minimize propulsion development cost and schedule risk by using proven engine technology.

### RFP-3.1.c.a: General Design – Materials (Functional)
Airframe must survive a decade of carrier/maritime operations without excessive maintenance.

### RFP-3.1.c.b: General Design – Materials (Functional)
Avoid schedule/cost risk from immature or scarce materials.

### RFP-3.1.d.a: General Design – Subsystems (Functional)
Avoid integrating immature technology that could delay IOC.

### RFP-3.2: Risk Tolerance (Functional)
The carrier and its crew must not be put at greater risk by adding this aircraft to the air wing. Even if the air vehicle can be lost, the carrier itself cannot be endangered by that loss.

### RFP-3.3.a: Carrier Suitability (Functional)
Operate from the carriers the Navy actually has and will have.

### RFP-3.3.b: Carrier Suitability (Functional)
Fit efficiently on a crowded flight/hangar deck alongside crewed aircraft.

### RFP-3.3.c.b: Carrier Suitability (Functional)
Communicate reliably with existing carrier deck-handling and ground-control infrastructure.

### RFP-3.3.d: Carrier Suitability (Functional)
Land safely and autonomously without relying on human piloting.

### RFP-3.3.1.a: Carrier Suitability – Launch (Functional)
Launch reliably even in adverse hot, calm-wind conditions.

### RFP-3.3.1.b: Carrier Suitability – Launch (Functional)
Leave the catapult safely under worst-case sink/control conditions.

### RFP-3.3.2.a: Carrier Suitability – Recovery (Functional)
Design the arresting hook/gear interface to a realistic engaging speed.

### RFP-3.3.2.b: Carrier Suitability – Recovery (Functional)
Approach at a controllable but not excessive speed.

### RFP-3.3.2.c: Carrier Suitability – Recovery (Functional)
Land with an operationally realistic fuel/store reserve.

### RFP-3.4.1.a: Payload – Air-to-Air (Functional)
Carry enough sensor/avionics capability to conduct the air-to-air mission.

### RFP-3.4.1.b.a: Payload – Air-to-Air (Functional)
Be lethal in the counter-air fighter-sweep role.

### RFP-3.4.2.a: Payload – Strike (Functional)
Carry enough sensor/avionics capability to conduct the strike mission.

### RFP-3.4.2.b.a: Payload – Strike (Functional)
Be lethal in the strike role.

### RFP-3.5.1.a: Mission – Air-to-Air (Functional)
Reach the fight and return, extending the air wing's reach.

### RFP-3.5.1.b: Mission – Air-to-Air (Functional)
Stay in the fight long enough to be tactically useful.

### RFP-3.5.1.d: Mission – Air-to-Air (Functional)
Close on or disengage from a target quickly when tactically necessary.

### RFP-3.5.2.a: Mission – Strike (Functional)
Reach strike targets and return.

### RFP-3.5.2.b: Mission – Strike (Functional)
Penetrate and egress contested airspace at low altitude.

### RFP-3.5.2.c: Mission – Strike (Functional)
Survive the low-altitude ingress/egress at adequate speed.

### RFP-3.6.a: Point Performance (Functional)
Withstand maneuvering loads expected in combat.

### RFP-3.6.b: Point Performance (Functional)
Carry a useful, flexible external stores loadout.

### RFP-3.6.c: Point Performance (Functional)
Launch using the catapults the fleet already has.

### RFP-3.6.d: Point Performance (Functional)
Recover using the arresting gear the fleet already has.

### RFP-3.6.e: Point Performance (Functional)
Survive an engine failure right after catapult launch, if multi-engine.

### RFP-3.6.f: Point Performance (Functional)
Survive an engine failure on approach, if multi-engine.

### RFP-3.6.g: Point Performance (Functional)
Fit within carrier elevator/hangar geometry when spread.

### RFP-3.6.h: Point Performance (Functional)
Fit within carrier elevator/hangar geometry when stowed.

### RFP-3.6.i: Point Performance (Functional)
Clear the jet blast deflector envelope like other embarked aircraft.

### RFP-3.6.j: Point Performance (Functional)
Fit inside the hangar bay.

### RFP-3.6.k: Point Performance (Functional)
Survive repeated arrested landings without hook failure.

### RFP-3.6.l: Point Performance (Functional)
Stay within a size/weight class the Navy considers affordable and deck-compatible.

### RFP-3.6.n: Point Performance (Functional)
Be certifiable and flyable under Navy airworthiness authority.

## #2: System Requirements (Container)

### SYS-001: Engine production/qualification status (Functional)
Engine(s) shall be an existing, currently-in-production design.

### SYS-002: Structural material qualified service life in a maritime environment (Functional)
≥10 years, with demonstrated resistance to moisture intrusion and salt spray.

### SYS-003: Material production availability (Functional)
All primary structural/system materials currently available in production quantities.

### SYS-004: Subsystem technology readiness level (TRL) (Functional)
TRL ≥ 6 for all subsystems (incl. avionics, mission systems) at design freeze.

### SYS-005: Incremental risk to host carrier (Functional)
No additional risk to the carrier beyond current air wing baseline.

### SYS-006: System redundancy/reliability sufficient to bound carrier risk (Functional)
Redundancy present such that assessed carrier risk is acceptable even given air-vehicle loss.

### SYS-007: Carrier class compatibility (Functional)
Operable from CVN-68 (Nimitz) and CVN-78 (Ford) class carriers.

### SYS-008: Stowed (wings-folded) planform spot factor (Functional)
≤ 0.8, where spot factor is measured relative to the F/A-18E/F Super Hornet reference planform per OPNAV 3710.7 carrier-suitability criteria.

### SYS-009: Reserved SWAP-C for MD-5 GCS / deck-handling comms (Functional)
Sufficient reserved size/weight/power/cooling margin to support MD-5 GCS and deck-handling system interfaces.

### SYS-010: Automatic landing guidance capability (Functional)
2-way JPALS (differential GPS) automatic carrier landing.

### SYS-011: Launch capability at max ambient temperature / zero WOD (Functional)
Capable of catapult launch at 89.8°F with 0 kt Wind Over Deck.

### SYS-012: Catapult minimum end airspeed (Functional)
Highest of: (1) CG sink ≤10 ft w/ deck run ≤32 ft, (2) 90% CLmax power-off OGE, (3) if multi-engine, min single-engine control speed.

### SYS-013: Arrestment engaging speed (relative to approach speed) (Functional)
Not less than 1.05 times the approach airspeed defined in SYS-014.

### SYS-014: Approach airspeed (Functional)
>10% above stall speed, and ≤145 kt.

### SYS-015: Arrestment design landing weight (Functional)
Includes 10-min loiter fuel at 10,000 ft + 2 landing attempts + 25% max fuel weight + 50% store weight.

### SYS-016: Internal avionics/sensor weight (A2A) (Functional)
≤ 1,000 lb internal weight allocated for air-to-air mission avionics and sensors.

### SYS-017: Air-to-air ordnance load (Functional)
2× AIM-120D.

### SYS-018: Internal avionics/sensor weight (strike) (Functional)
≤ 1,000 lb internal weight allocated for strike-mission avionics and sensors.

### SYS-019: Strike ordnance load (Functional)
4× GBU-53/B Small Diameter Bomb II.

### SYS-020: Combat radius (A2A mission) (Functional)
≥500 nm. (700 nm desirable — tracked as a Measure of Merit.)

### SYS-021: Max-thrust combat persistence at best-turn speed, 10,000 ft (A2A) (Functional)
≥2 min. (5 min desirable — MoM.)

### SYS-022: Dash speed at 30,000 ft (A2A) (Functional)
≥ Mach 0.8. (Mach 0.95 desirable — MoM.)

### SYS-023: Combat radius (strike mission) (Functional)
≥500 nm. (700 nm desirable — MoM.)

### SYS-024: Sea-level ingress/egress dash distance & thrust setting (strike) (Functional)
50 nm at intermediate (max non-afterburning) thrust.

### SYS-025: Sea-level dash speed (strike) (Functional)
≥ Mach 0.8. (Mach 0.90 desirable — MoM.)

### SYS-026: Design vertical load factor (Nz) at mid-mission weight (Functional)
≥ 5g.

### SYS-027: External store carriage capacity (Functional)
≥1,000 lb total; ≥400 lb per single station.

### SYS-028: Launch performance vs. WOD, using C-13-2 catapult (Functional)
Achievable with WOD ≤ 0 kt.

### SYS-029: Recovery performance vs. WOD, using Mark 7 Mod 3 gear (Functional)
Achievable with WOD ≤ 15 kt.

### SYS-030: Single-engine rate of climb (SEROC) at launch (Functional)
≥200 ft/min.

### SYS-031: Single-engine rate of climb (SEROC) on approach (Functional)
≥500 ft/min.

### SYS-032: Unfolded wingspan (Functional)
≤60 ft.

### SYS-033: Folded wingspan (Functional)
≤ 35 ft, measured wings-folded per NAVAIR carrier elevator/hangar clearance criteria.

### SYS-034: Overall aircraft length (Functional)
≤ F-35C overall length.

### SYS-035: Overall height, wings folded (Functional)
≤18.5 ft.

### SYS-036: Arresting hook design strength (Functional)
≥200,000 lbf.

### SYS-037: Maximum takeoff gross weight (Functional)
≤60,000 lb.

### SYS-038: Airworthiness certification compliance (Functional)
Meets NAVAIR airworthiness requirements (NAVAIRINST 13034.1 flight clearance; MIL-HDBK-516D criteria).

## #3: Subsystem Requirements (Container)

### SUB-001: Engine qualification/type-certificate status (Functional)
Candidate engines limited to those with an existing DoD or commercial type certificate/qualification.
- Rationale: Minimize propulsion development cost and schedule risk (refines SYS-001).

### SUB-002: Structural material corrosion/marine qualification (Functional)
MIL-HDBK-5/MMPDS-qualified alloys (e.g., 7075-T7351 aluminum, Ti-6Al-4V titanium) with documented salt-spray corrosion resistance per ASTM B117.
- Rationale: Survive a decade of maritime exposure without excessive maintenance (refines SYS-002/003).

### SUB-003: Line-replaceable unit (LRU) TRL qualification record (Functional)
Sourced exclusively from vendors with a documented TRL ≥ 6 per DoD TRL definitions (existing production or flight-qualified line-replaceable units).
- Rationale: Avoid immature avionics technology (refines SYS-004).

### SUB-004: Control-surface actuation & command-link redundancy level (Functional)
≥ 1 level of redundancy in primary flight-control actuation.
- Rationale: Bound carrier risk through actuation redundancy (refines SYS-005/006).

### SUB-005: Lost-link / fail-safe autonomy behavior (Functional)
Automatic return-to-marshal or safe-ditch behavior requiring no deck intervention.
- Rationale: Bound carrier risk if the air vehicle is lost (refines SYS-005/006).

### SUB-006: Outer mold line / wing-fold geometry (Functional)
Unfolded span ≤60 ft, folded span ≤35 ft, length ≤ F-35C length, folded height ≤18.5 ft — simultaneously.
- Rationale: Fit carrier elevator/hangar geometry (refines SYS-007, SYS-032–035).

### SUB-007: Stowed planform area relative to benchmark (Functional)
Stowed planform area ≤ 0.8 times the F/A-18E/F Super Hornet reference spot factor (consistent with SYS-008).
- Rationale: Fit efficiently on a crowded deck (refines SYS-008).

### SUB-008: Avionics data-bus bandwidth/interface reservation (Functional)
MIL-STD-1553C bus with reserved I/O for MD-5 GCS & deck-handling interfaces. Caveat: may need a supplemental high-bandwidth bus for sensor/autonomy data.
- Rationale: Communicate with MD-5 GCS / deck systems (refines SYS-009).

### SUB-009: Navigation subsystem JPALS/datalink integration (Functional)
Integrated JPALS-compatible DGPS receiver + 2-way datalink.
- Rationale: Land automatically via JPALS (refines SYS-010).

### SUB-010: Wing/high-lift sizing vs. catapult end-speed condition (Functional)
Meets the governing catapult end-speed case (highest of the SYS-012 CG-sink, CLmax, and single-engine-control criteria) at max design takeoff weight, 89.8°F Day, 0 kt WOD.
- Rationale: Leave the catapult safely (refines SYS-011/012).

### SUB-011: Landing gear & hook design condition (Functional)
Designed to arrestment landing weight at engaging speed = 1.05–1.15× stall, ≤145 kt approach.
- Rationale: Land within an operationally realistic weight/speed envelope (refines SYS-013–015).

### SUB-012: Mission-systems bay weight/volume allocation (Functional)
1,000 lb weight allocation plus adequate volume, common to both missions.
- Rationale: Carry mission avionics for both mission profiles (refines SYS-016/018).

### SUB-013: Weapons bay/station capacity & compatibility (Functional)
Internal/external accommodation of 2×AIM-120D or 4×GBU-53/B; external stations ≥400 lb, ≥1,000 lb total. Confirm internal-vs-external split with team.
- Rationale: Carry lethal payload for both missions (refines SYS-017/019/027).

### SUB-014: Usable fuel fraction vs. combat radius (Functional)
Sufficient fuel for a 500 nm combat radius, both missions. High-priority carpet-plot driver.
- Rationale: Reach combat radius on both missions (refines SYS-020/023).

### SUB-015: Sustained thrust duration capability (Functional)
Sustains max (A2A) / intermediate (strike) thrust for the required combat-persistence durations without exceeding thermal/fuel-flow limits.
- Rationale: Sustain combat persistence on both missions (refines SYS-021/024).

### SUB-016: Airframe/propulsion dash-speed capability (Functional)
Sustains Mach 0.8 at 30,000 ft without exceeding structural/thermal limits.
- Rationale: Achieve dash speed at altitude (refines SYS-022).

### SUB-017: Primary structure (wing/fuselage/hook fitting) design condition (Functional)
5g limit load at mid-mission weight; hook fitting reacts ≥200,000 lbf; within a 60,000 lb MTOW budget. High-priority structural driver.
- Rationale: Withstand design loads and hook loads within the weight budget (refines SYS-026/036/037).

### SUB-018: Launch performance vs. published C-13-2 chart (Functional)
Verified against the C-13-2 catapult performance chart (RFP Fig. 2) at design launch weight.
- Rationale: Launch on fielded carrier equipment (refines SYS-028).

### SUB-019: One-engine-inoperative climb performance (Functional)
200 ft/min (launch) and 500 ft/min (approach), one-engine-inoperative.
- Rationale: Survive an engine-out condition, if multi-engine (refines SYS-030/031).

### SUB-020: Design/verification process compliance (Functional)
Follows NAVAIRINST 13034.1 flight-clearance review and MIL-HDBK-516D airworthiness criteria.
- Rationale: Be certifiable under Navy airworthiness authority (refines SYS-038).
